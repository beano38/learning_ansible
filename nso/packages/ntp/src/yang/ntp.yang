module ntp {

  namespace "http://example.com/ntp";
  prefix ntp;

  import ietf-inet-types {prefix inet;}
  import tailf-common {prefix tailf;}
  import tailf-ncs {prefix ncs;}

  description
    "NTP Service";

  revision 2016-01-01 {
    description
      "Initial revision.";
  }

  list ntp {
    description "This is an RFS skeleton service";

    key name;
    leaf name {
      tailf:info "Unique service id";
      tailf:cli-allow-range;
      type string;
    }

    uses ncs:service-data;
    ncs:servicepoint ntp-servicepoint;

    // may replace this with other ways of refering to the devices.
    leaf-list device {
      tailf:info "Devices to add to NTP service";
      type leafref {
        path "/ncs:devices/ncs:device/ncs:name";
      }
    }

    leaf ntp_server {
      tailf:info "IPv4 Address of NTP Server";
      type string;
    }
  }
}
